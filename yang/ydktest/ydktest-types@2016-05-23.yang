module ydktest-types {

  namespace "http://cisco.com/ns/yang/ydktest-types";

  prefix "types";

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for sanity package.

     This module contains definitions
     for the following management objects:
    

     Copyright (c) 2013-2014 by Cisco Systems, Inc.
     All rights reserved.";

  revision "2016-05-23" {
    description
      "Initial revision.";
  }

  identity YDK_IDENTITY {
    description
      "YDK identity";    
  }

  typedef Ydk-Simple-Union-type {
      type union {
          type uint32;
          type string;
      }
      description "Simple int & string union type";
  }
  
  typedef Ydk-Recursive-Union-type {
      type union {
          type Ydk-Simple-Union-type;
          type int8;
      }
      description "Union of union types";
  }
  
  typedef Ydk-String-type {
      type string;
      description "String type";
  }
  
  typedef Ydk-Identity-type {
      type identityref {
          base YDK_IDENTITY;
      }
      description "Identityref type";
  }
 
  typedef Ydk-bits-type {
    description "this is bits type value";
    type bits {
      bit disable-nagle {
        position 0;
      }
      bit auto-sense-speed {
        position 1;
      }
    }
  }

}
